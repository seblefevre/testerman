-- $Id: SS-Errors.asn 24270 2008-02-05 06:10:34Z etxrab $
-- 3GPP TS 24.080 V7.4.0 (2007-09)
-- 4.3.1	Errors ASN.1 specification
-- The following ASN.1 module provides an ASN.1 specification of errors. Errors from MAP are imported in the SS Protocol module in subclause 4.5. The module defines errors by allocating them a local value. For the involved errors the same local values as in MAP are allocated.

SS-Errors {
   itu-t identified-organization (4) etsi (0) mobileDomain (0) gsm-Access (2) modules (3)
   ss-Errors (1) version10 (10)}

DEFINITIONS ::=

BEGIN

IMPORTS

ERROR FROM
Remote-Operations-Information-Objects {joint-iso-itu-t remote-operations(4)
  informationObjects(5) version1(0)};

-- The MAP errors
-- unknownSubscriber, bearerServiceNotProvisioned, teleserviceNotProvisioned,
-- illegalSS-Operation, ss-ErrorStatus, ss-NotAvailable, ss-SubscriptionViolation,
-- ss-Incompatibility, systemFailure, dataMissing, unexpectedDataValue, facilityNotSupported,
-- pw-RegistrationFailure, negativePW-Check, callBarred, numberOfPW-AttemptsViolation,
-- absentSubscriber, illegalSubscriber, illegalEquipment, ussd-Busy, unknownAlphabet,
-- forwardingViolation, forwardingFailed
-- are imported from MAP-Errors in SS-Protocol module.

-- errors definition
resourcesNotAvailable  ERROR ::= {
	CODE	local:127 }
maxNumberOfMPTY-ParticipantsExceeded  ERROR ::= {
	CODE	local:126 }
invalidDeflectedToNumber  ERROR ::= {
	CODE	local:125 }
specialServiceCode  ERROR ::= {
	CODE	local:124 }
deflectionToServedSubscriber  ERROR ::= {
	CODE	local:123 }
rejectedByNetwork  ERROR ::= {
	CODE	local:122 }
rejectedByUser  ERROR ::= {
	CODE	local:121 }

END
