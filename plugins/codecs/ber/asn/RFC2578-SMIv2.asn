--------------------------------------------------------------------------------
-- SNMP v2c ASN.1, adapted for Testerman.
-- Based on RFC 1901 (SNMPv2c message)
-- including RFC 1905 (SNMPv2 PDUs),
-- itself relying on RFC 2578 (SNMPv2-SMI)
--------------------------------------------------------------------------------


COMMUNITY-BASED-SNMPv2 DEFINITIONS ::= BEGIN


--------------------------------------------------------------------------------
-- Inline import from RFC2578
--------------------------------------------------------------------------------

--     IMPORTS
--         ObjectName, ObjectSyntax, Integer32
--             FROM SNMPv2-SMI;


ObjectName ::=
    OBJECT IDENTIFIER

NotificationName ::=
    OBJECT IDENTIFIER

-- syntax of objects

-- the "base types" defined here are:
--   3 built-in ASN.1 types: INTEGER, OCTET STRING, OBJECT IDENTIFIER
--   8 application-defined types: Integer32, IpAddress, Counter32,
--              Gauge32, Unsigned32, TimeTicks, Opaque, and Counter64

ObjectSyntax ::=
    CHOICE {
        simple
            SimpleSyntax,

          -- note that SEQUENCEs for conceptual tables and
          -- rows are not mentioned here...

        application-wide
            ApplicationSyntax
    }
-- built-in ASN.1 types

SimpleSyntax ::=
    CHOICE {
        -- INTEGERs with a more restrictive range
        -- may also be used
        integer-value               -- includes Integer32
            INTEGER (-2147483648..2147483647),

        -- OCTET STRINGs with a more restrictive size
        -- may also be used
        string-value
            OCTET STRING (SIZE (0..65535)),

        objectID-value
            OBJECT IDENTIFIER
    }

-- indistinguishable from INTEGER, but never needs more than
-- 32-bits for a two's complement representation
Integer32 ::=
        INTEGER (-2147483648..2147483647)


-- application-wide types

ApplicationSyntax ::=
    CHOICE {
        ipAddress-value
            IpAddress,

        counter-value
            Counter32,

        timeticks-value
            TimeTicks,

        arbitrary-value
            Opaque,

        big-counter-value
            Counter64,

        unsigned-integer-value  -- includes Gauge32
            Unsigned32
    }

-- in network-byte order
-- (this is a tagged type for historical reasons)
IpAddress ::=
    [APPLICATION 0]
        IMPLICIT OCTET STRING (SIZE (4))

-- this wraps
Counter32 ::=
    [APPLICATION 1]
        IMPLICIT INTEGER (0..4294967295)

-- this doesn't wrap
Gauge32 ::=
    [APPLICATION 2]
        IMPLICIT INTEGER (0..4294967295)

-- an unsigned 32-bit quantity
-- indistinguishable from Gauge32
Unsigned32 ::=
    [APPLICATION 2]
        IMPLICIT INTEGER (0..4294967295)

-- hundredths of seconds since an epoch
TimeTicks ::=
    [APPLICATION 3]
        IMPLICIT INTEGER (0..4294967295)

-- for backward-compatibility only
Opaque ::=
    [APPLICATION 4]
        IMPLICIT OCTET STRING

-- for counters that wrap in less than one hour with only 32 bits
Counter64 ::=
    [APPLICATION 6]
        IMPLICIT INTEGER (0..18446744073709551615)


--------------------------------------------------------------------------------
-- RFC1905 follows
--------------------------------------------------------------------------------

-- protocol data units

PDUs ::=
   CHOICE {
       get-request
           GetRequest-PDU,

       get-next-request
           GetNextRequest-PDU,

       get-bulk-request
           GetBulkRequest-PDU,

       response
           Response-PDU,

       set-request
           SetRequest-PDU,

       inform-request
           InformRequest-PDU,

       snmpV2-trap
           SNMPv2-Trap-PDU,

       report
           Report-PDU
   }


-- PDUs

GetRequest-PDU ::=
   [0]
       IMPLICIT PDU

GetNextRequest-PDU ::=
   [1]
       IMPLICIT PDU

Response-PDU ::=
   [2]
       IMPLICIT PDU

SetRequest-PDU ::=
   [3]
       IMPLICIT PDU

-- [4] is obsolete

GetBulkRequest-PDU ::=
   [5]
       IMPLICIT BulkPDU

InformRequest-PDU ::=
   [6]
       IMPLICIT PDU

SNMPv2-Trap-PDU ::=
   [7]
       IMPLICIT PDU

--   Usage and precise semantics of Report-PDU are not presently
--   defined.  Any SNMP administrative framework making use of
--   this PDU must define its usage and semantics.
Report-PDU ::=
   [8]
       IMPLICIT PDU

-- max-bindings INTEGER ::= 2147483647




PDU ::=
   SEQUENCE {
       request-id
           Integer32,

       error-status            -- sometimes ignored
           INTEGER {
               noError(0),
               tooBig(1),
               noSuchName(2),   -- for proxy compatibility
               badValue(3),     -- for proxy compatibility
               readOnly(4),     -- for proxy compatibility
               genErr(5),
               noAccess(6),
               wrongType(7),
               wrongLength(8),
               wrongEncoding(9),
               wrongValue(10),
               noCreation(11),
               inconsistentValue(12),
               resourceUnavailable(13),
               commitFailed(14),
               undoFailed(15),
               authorizationError(16),
               notWritable(17),
               inconsistentName(18)
           },

       error-index            -- sometimes ignored
           INTEGER (0..2147483647),

       variable-bindings   -- values are sometimes ignored
           VarBindList
   }


BulkPDU ::=                     -- MUST be identical in
   SEQUENCE {                  -- structure to PDU
       request-id
           Integer32,

       non-repeaters
           INTEGER (0..2147483647),

       max-repetitions
           INTEGER (0..2147483647),

       variable-bindings       -- values are ignored
           VarBindList
   }


-- variable binding

VarBind ::=
   SEQUENCE {
       name
           ObjectName,

       choice CHOICE { -- the 'choice' name is added for Testerman
           value
               ObjectSyntax,

           unSpecified         -- in retrieval requests
                   NULL,

                               -- exceptions in responses
           noSuchObject[0]
                   IMPLICIT NULL,

           noSuchInstance[1]
                   IMPLICIT NULL,

           endOfMibView[2]
                   IMPLICIT NULL
       }
   }


-- variable-binding list

VarBindList ::=
   SEQUENCE (SIZE (0..2147483647)) OF
       VarBind


--------------------------------------------------------------------------------
-- RFC1901 follows
--------------------------------------------------------------------------------

-- top-level message

Message ::=
        SEQUENCE {
             version
                INTEGER {
                    version(1)  -- modified from RFC 1157
                },

            community           -- community name
                OCTET STRING,

            data                -- PDUs as defined in [4]
                PDUs            -- Adapted for Testerman: ANY is replaced with PDUs
        }


END
